MinimalCertificateExample DEFINITIONS EXPLICIT TAGS ::= BEGIN

AlgorithmIdentifier ::= SEQUENCE {
  algorithm OBJECT IDENTIFIER,
  parameters NULL OPTIONAL
}

AttributeTypeAndValue ::= SEQUENCE {
  type OBJECT IDENTIFIER,
  value DirectoryString
}

DirectoryString ::= CHOICE {
  utf8String UTF8String,
  printableString PrintableString
}

RelativeDistinguishedName ::= SET OF AttributeTypeAndValue

RDNSequence ::= SEQUENCE OF RelativeDistinguishedName
Name ::= CHOICE {
  rdnSequence RDNSequence
}

Time ::= CHOICE {
  utcTime UTCTime,
  generalTime GeneralizedTime
}

Validity ::= SEQUENCE {
  notBefore Time,
  notAfter Time
}

SubjectPublicKeyInfo ::= SEQUENCE {
  algorithm AlgorithmIdentifier,
  subjectPublicKey BIT STRING
}

Extension ::= SEQUENCE {
  extnID OBJECT IDENTIFIER,
  critical BOOLEAN DEFAULT FALSE,
  extnValue OCTET STRING
}

Extensions ::= SEQUENCE OF Extension

Version ::= INTEGER {
  v1(0),
  v2(1),
  v3(2)
}

TBSCertificate ::= SEQUENCE {
  version [0] EXPLICIT Version DEFAULT v1,
  serialNumber INTEGER,
  signature AlgorithmIdentifier,
  issuer Name,
  validity Validity,
  subject Name,
  subjectPublicKeyInfo SubjectPublicKeyInfo,
  extensions [3] EXPLICIT Extensions OPTIONAL
}

Certificate ::= SEQUENCE {
  tbsCertificate TBSCertificate,
  signatureAlgorithm AlgorithmIdentifier,
  signatureValue BIT STRING
}

END
