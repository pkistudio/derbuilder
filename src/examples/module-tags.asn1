ImplicitHeaderExample DEFINITIONS IMPLICIT TAGS ::= BEGIN

Version ::= INTEGER {
  v1(0),
  v2(1),
  v3(2)
}

VersionedSerial ::= SEQUENCE {
  version [0] Version DEFAULT v1,
  serialNumber INTEGER
}

END
